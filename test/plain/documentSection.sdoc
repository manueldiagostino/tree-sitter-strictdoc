[DOCUMENT]
MID: c2d4542d5f1741c88dfcb4f68ad7dcbd
TITLE: User Guide
UID: SDOC_UG
VERSION: Git commit: @GIT_VERSION, Git branch: @GIT_BRANCH
DATE: @GIT_COMMIT_DATETIME
OPTIONS:
  ENABLE_MID: True
  VIEW_STYLE: Inline
  NODE_IN_TOC: True
METADATA:
  KEY1: True
  KEY2: True

[GRAMMAR]
ELEMENTS:
- TAG: SECTION
  PROPERTIES:
    IS_COMPOSITE: True
    PREFIX: None
    VIEW_STYLE: Narrative
  FIELDS:
  - TITLE: MID
    TYPE: String
    REQUIRED: False
  - TITLE: UID
    TYPE: String
    REQUIRED: False
  - TITLE: ASIL
    TYPE: SingleChoice(A, B, C, D)
    REQUIRED: True

[DOCUMENT_FROM_FILE]
FILE: ./ahsjdak.sdoc

[SECTION]
MID: 75a595ff028741d0bf9067bba8fb787a
TITLE: Introduction

[/SECTION]

[[COMPOSITE]]
FIELD_A: Single line field_name
FIELD_B: >>>
This is a normal string, I can write multi line
strings with symbols "<,<<,[" and also special words such as:
[ANCHOR] or [LINK].

[ANCHOR: ANCHOR-EXAMPLE]

I'm also able to insert inline_links [LINK: ANCHOR_EXAMPLE].
<<<
FIELD_C: [ANCHOR: ANCHOR-EXAMPLE]
FIELD_D: A single line text part with multiple [LINK: ABC], [LINK: ABCD] inside.

[[/COMPOSITE]]
